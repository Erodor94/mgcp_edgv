FME workspace fme_mapeamento_MGCP_2_EDGV_30.fmw

Parameters:
- direcao = volta   # Direção do mapeamento
- JsonMapeamento = $(FME_MF_DIR)Novo_MGCP-EDGV_sem_obs_para_teste.json   # Arquivo de mapeamento
- DestDataset_POSTGIS = edgv   # Database
- COORDSYS = EPSG:4326   # Coordinate System
- SourceDataset_POSTGIS = asc_50k_gothic_sad_21s   # Database
- SourceDataset_ESRISHAPE = $(FME_MF_DIR)W058S21.zip   # Source Esri Shapefile(s)
- FEATURE_TYPES = AAJ030 AAL015 ABA030 ABH080 ABH090 ABH130 ABH140 AEB010 AEB020 AEC030 AED010 AED020 AGB005 AGB015 AGB055 LAP010 LAP030 LAP050 LAQ040 LAQ070 LBH030 LBH070 LBH140 LBI020 PAJ030 PAL015 PAL019 PAL020 PAL099 PAL241 PAM020 PAM070 PAQ065 PBH070 PBH145 PBH170 PBI010 PGB230 PZD040
- SourceDataset_ESRISHAPE_3 = $(FME_MF_DIR)MGCP\W058S21\PBH145.shp   # Source Esri Shapefile(s)
- DestDataset_POSTGIS_4 = edgv_3   # Connection

Readers:
- POSTGIS_1: POSTGIS from $(SourceDataset_POSTGIS)
- ESRISHAPE_1: ESRISHAPE from $(SourceDataset_ESRISHAPE)
- ESRISHAPE_2: ESRISHAPE from $(SourceDataset_ESRISHAPE_3)

Writers:
- POSTGIS_2: POSTGIS to $(DestDataset_POSTGIS)
- POSTGIS_3: POSTGIS to $(DestDataset_POSTGIS_4)

PBH145 (reader ESRISHAPE_2)
    attributes: FCODE char(5), UID char(36), WST long, ACC long, CCN char(254), SDV char(20), SDP char(254), SRT long, TXT char(254)
    -> CoordinateSystemSetter
Note: ffs está sem sistema
CoordinateSystemSetter
    COORDSYS = $(COORDSYS)
    -> PythonCaller
PythonCaller
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              file = open(mappingPath, 'r')
              data = file.read()
              mapDict = json.loads(data)
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          featDict[attr] = feature.getAttribute(attr)
                      else:
                          featDict[attr] = None
              if feature.performFunction('@GeometryType()') == 'fme_polygon':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              return featDict

          def evaluateExpression(self, featDict, expression):
              return expression["nome_atributo"] in featDict and featDict[expression["nome_atributo"]] == expression["valor"]

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  default_key = "atributos_default_ida"
                  filter_key = "filtro_ida"
                  key_class_origin = "classe_ida"
                  key_class_destiny = "classe_volta"
                  key_group_origin = "tupla_ida"
                  key_group_destiny = "tupla_volta"
              else:
                  key_attr_origin = "attr_volta"
                  key_attr_destiny = "attr_ida"
                  key_value_origin = "valor_volta"
                  key_value_destiny = "valor_ida"
                  default_key = "atributos_default_volta"
                  filter_key = "filtro_volta"
                  key_class_origin = "classe_volta"
                  key_class_destiny = "classe_ida"
                  key_group_origin = "tupla_volta"
                  key_group_destiny = "tupla_ida"

              should_map = False
              for classmap in self.mappingDict['mapeamento_classes']:
                  if "sentido" not in classmap or ("sentido" in classmap and classmap["sentido"] == self.mappingType):
                      if classmap[key_class_origin] == featDict["fme_feature_type"]:
                          should_map = True
              if not should_map:
                  featDict["CLASS_NOT_FOUND"] = True
                  return featDict

              mappedFeat = copy.deepcopy(featDict)

              for attmap in self.mappingDict['mapeamento_atributos']:
                  if attmap[key_attr_origin] in featDict:
                      mappedFeat[attmap[key_attr_destiny]] = featDict[attmap[key_attr_origin]]
                      if "traducao" in attmap:
                          for valuemap in attmap["traducao"]:
                              if valuemap[key_value_origin] == featDict[attmap[key_attr_origin]] and ("sentido" not in valuemap or ("sentido" in valuemap and valuemap["sentido"] == self.mappingType)):
                                  mappedFeat[attmap[key_attr_destiny]] = valuemap[key_value_destiny]

              for classmap in self.mappingDict['mapeamento_classes']:
                  if "sentido" not in classmap or ("sentido" in classmap and classmap["sentido"] == self.mappingType):
                      if classmap[key_class_origin] == featDict["fme_feature_type"]:
                          if filter_key in classmap:
                              if not self.evaluateFilter(featDict, classmap[filter_key]):
                                  continue

                          mappedFeat["fme_feature_type"] = classmap[key_class_destiny]

                          if default_key in classmap:
                              for default in classmap[default_key]:
                                  mappedFeat[default["nome_atributo"]] = default["valor"]

                          if "traducao_atributos" in classmap:
                              for attmap in classmap['traducao_atributos']:
                                  if attmap[key_attr_origin] in featDict:
                                      if attmap[key_attr_destiny] not in mappedFeat:
                                          mappedFeat[attmap[key_attr_destiny]] = featDict[attmap[key_attr_origin]]
                                      if "traducao" in attmap:
                                          for valuemap in attmap["traducao"]:
                                              if valuemap[key_value_origin] == featDict[attmap[key_attr_origin]] and ("sentido" not in valuemap or ("sentido" in valuemap and valuemap["sentido"] == self.mappingType)):
                                                  mappedFeat[attmap[key_attr_destiny]] = valuemap[key_value_destiny]

                          if "mapeamento_atributos" in classmap:
                              for attmap in classmap['mapeamento_atributos']:
                                  if "sentido" not in attmap or ("sentido" in attmap and attmap["sentido"] == self.mappingType):
                                      if all([self.evaluateExpression(featDict, condition) for condition in attmap[key_group_origin]]):
                                          for valuemap in attmap[key_group_destiny]:
                                              mappedFeat[valuemap["nome_atributo"]] = valuemap["valor"]
                          break

              return mappedFeat

          def mapDictToFeature(self, feat, featDict):
              for attr, value in featDict.iteritems():
                  if value or value == 0:
                      feat.setAttribute(attr, u'{0}'.format(value))
                  else:
                      feat.setAttribute(attr, None)
              return feat

          def input(self,feature):
              feat = self.buildFeatureDict(feature)
              outputFeatDict = self.convertFeature(feat)
              if "CLASS_NOT_FOUND" in outputFeatDict and not outputFeatDict["CLASS_NOT_FOUND"]:
                  feature.setAttribute("CLASS_NOT_FOUND", u'True')
                  self.pyoutput(feature)
              else:
                  outputFeature = self.mapDictToFeature(feature, outputFeatDict)
                  self.pyoutput(outputFeature)

          def close(self):
              pass
    PYTHONSYMBOL = FeatureProcessor
    -> Tester_4
Tester_4
    BOOL_OP = OR
    COMPOSITE_TEST = 1
    TEST_CLAUSE = TEST @Value(CLASS_NOT_FOUND) = True
    TEST_MODE = TEST
    PASSED -> Tester_4_Passed
    FAILED -> Counter
Tester_4_Passed: Inspector
Table1 (writer POSTGIS_2)
hid_sumidouro_vertedouro_p (writer POSTGIS_3)
    attributes: id serial, causa int2, geometriaaproximada int2, nome varchar(255), tiposumvert int2
AAJ030 (reader ESRISHAPE_1) [off]
    attributes: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

Bookmark: DSGTools as geometrias são multi
Counter
    CNT_ATTR = _count
    DOMAIN = counter
    SCOPE = Global
    START = 0
    -> Aggregator
Aggregator
    ACCUM_ATTRS_NAME = Use Attributes From One Feature
    AGGREGATE_TYPE = Homogeneous Collection (If Possible)
    GROUP_BY = _count
    MODE = Geometry - Assemble One Level
    ORDERED = Yes
    SEP = ,
    AGGREGATE -> GeometryFilter

Bookmark: Quebra as classes por tipo de geometria e ajusta o fme_feature_type de acordo
GeometryFilter
    BREAK_AGG = No
    GEOM_PORT_NAMES = Point Line Area
    POINT -> AttributeCreator
    LINE -> AttributeCreator_2
    AREA -> AttributeCreator_3
AttributeCreator
    ATTR_TABLE = SET_TO fme_feature_type = @Value(fme_feature_type)_p
    -> hid_sumidouro_vertedouro_p (writer POSTGIS_3)
    -> Table1 (writer POSTGIS_2)
AttributeCreator_2
    ATTR_TABLE = SET_TO fme_feature_type = @Value(fme_feature_type)_l
    -> hid_sumidouro_vertedouro_p (writer POSTGIS_3)
    -> Table1 (writer POSTGIS_2)
AttributeCreator_3
    ATTR_TABLE = SET_TO fme_feature_type = @Value(fme_feature_type)_a
    -> hid_sumidouro_vertedouro_p (writer POSTGIS_3)
    -> Table1 (writer POSTGIS_2)
