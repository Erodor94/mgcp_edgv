FME workspace fme_mapeamento_MGCP_2_EDGV_30_volta (backup).fmw

Parameters:
- direcao = volta   # Direção do mapeamento
- JsonMapeamento = $(FME_MF_DIR)Novo_MGCP-EDGV_final_2019-07-08.json   # Arquivo de mapeamento
- SourceDataset_POSTGIS = edgv_pid   # Connection
- FEATURE_TYPES = edgv.aer_pista_ponto_pouso_a edgv.aer_pista_ponto_pouso_l edgv.aer_pista_ponto_pouso_p edgv.aux_descontinuidade_geometrica_l edgv.aux_descontinuidade_geometrica_p edgv.aux_moldura_a edgv.cbge_area_agropec_ext_veg_pesca_a edgv.cbge_area_construida_a edgv.cbge_area_de_propriedade_particular_a edgv.cbge_area_duto_a edgv.cbge_area_habitacional_a edgv.cbge_area_uso_especifico_a edgv.cbge_canteiro_central_a edgv.cbge_canteiro_central_l edgv.cbge_cemiterio_a edgv.cbge_cemiterio_p edgv.cbge_delimitacao_fisica_l edgv.cbge_deposito_geral_a edgv.cbge_deposito_geral_p edgv.cbge_entroncamento_area_a edgv.cbge_espelho_dagua_a edgv.cbge_estacionamento_a edgv.cbge_largo_a edgv.cbge_passeio_a edgv.cbge_passeio_l edgv.cbge_poste_p edgv.cbge_praca_a edgv.cbge_quadra_a edgv.cbge_retorno_l edgv.cbge_retorno_p edgv.cbge_trecho_arruamento_a edgv.cbge_trecho_arruamento_l edgv.dut_galeria_bueiro_l edgv.dut_galeria_bueiro_p edgv.dut_trecho_duto_l edgv.eco_equip_agropec_a edgv.eco_equip_agropec_l edgv.eco_equip_agropec_p edgv.eco_ext_mineral_a edgv.eco_ext_mineral_p edgv.eco_plataforma_a edgv.eco_plataforma_p edgv.edf_banheiro_publico_a edgv.edf_banheiro_publico_p edgv.edf_edif_abast_agua_a edgv.edf_edif_abast_agua_p edgv.edf_edif_agropec_ext_veg_pesca_a edgv.edf_edif_agropec_ext_veg_pesca_p edgv.edf_edif_comerc_serv_a edgv.edf_edif_comerc_serv_p edgv.edf_edif_comunic_a edgv.edf_edif_comunic_p edgv.edf_edif_constr_aeroportuaria_a edgv.edf_edif_constr_aeroportuaria_p edgv.edf_edif_constr_est_med_fen_a edgv.edf_edif_constr_est_med_fen_p edgv.edf_edif_constr_lazer_a edgv.edf_edif_constr_lazer_p edgv.edf_edif_constr_portuaria_a edgv.edf_edif_constr_portuaria_p edgv.edf_edif_constr_turistica_a edgv.edf_edif_constr_turistica_p edgv.edf_edif_desenv_social_a edgv.edf_edif_desenv_social_p edgv.edf_edif_energia_a edgv.edf_edif_energia_p edgv.edf_edif_ensino_a edgv.edf_edif_ensino_p edgv.edf_edif_ext_mineral_a edgv.edf_edif_ext_mineral_p edgv.edf_edif_industrial_a edgv.edf_edif_industrial_p edgv.edf_edif_metro_ferroviaria_a edgv.edf_edif_metro_ferroviaria_p edgv.edf_edif_policia_a edgv.edf_edif_policia_p edgv.edf_edif_pub_civil_a edgv.edf_edif_pub_civil_p edgv.edf_edif_pub_militar_a edgv.edf_edif_pub_militar_p edgv.edf_edif_religiosa_a edgv.edf_edif_religiosa_p edgv.edf_edif_residencial_a edgv.edf_edif_residencial_p edgv.edf_edif_rodoviaria_a edgv.edf_edif_rodoviaria_p edgv.edf_edif_saneamento_a edgv.edf_edif_saneamento_p edgv.edf_edif_saude_a edgv.edf_edif_saude_p edgv.edf_edif_servico_social_a edgv.edf_edif_servico_social_p edgv.edf_edificacao_a edgv.edf_edificacao_p edgv.edf_hab_indigena_a edgv.edf_hab_indigena_p edgv.edf_posto_combustivel_a edgv.edf_posto_combustivel_p edgv.edf_posto_fiscal_a edgv.edf_posto_fiscal_p edgv.edf_posto_guarda_municipal_a edgv.edf_posto_guarda_municipal_p edgv.edf_posto_policia_militar_a edgv.edf_posto_policia_militar_p edgv.edf_posto_policia_rod_federal_a edgv.edf_posto_policia_rod_federal_p edgv.edf_representacao_diplomatica_a edgv.edf_representacao_diplomatica_p edgv.emu_acesso_a edgv.emu_acesso_l edgv.emu_acesso_p edgv.emu_ciclovia_l edgv.emu_elevador_a edgv.emu_elevador_l edgv.emu_elevador_p edgv.emu_escadaria_a edgv.emu_escadaria_l edgv.emu_escadaria_p edgv.emu_poste_sinalizacao_p edgv.emu_rampa_a edgv.emu_rampa_l edgv.emu_rampa_p edgv.enc_aerogerador_p edgv.enc_antena_comunic_p edgv.enc_casa_de_forca_p edgv.enc_central_geradora_eolica_a edgv.enc_central_geradora_eolica_l edgv.enc_central_geradora_eolica_p edgv.enc_est_gerad_energia_eletrica_a edgv.enc_est_gerad_energia_eletrica_l edgv.enc_est_gerad_energia_eletrica_p edgv.enc_grupo_transformadores_a edgv.enc_grupo_transformadores_p edgv.enc_hidreletrica_a edgv.enc_hidreletrica_l edgv.enc_hidreletrica_p edgv.enc_subest_transm_distrib_energia_eletrica_a edgv.enc_termeletrica_a edgv.enc_termeletrica_p edgv.enc_torre_comunic_p edgv.enc_torre_energia_p edgv.enc_trecho_comunic_l edgv.enc_trecho_energia_l edgv.enc_zona_linhas_energia_comunicacao_a edgv.fer_cremalheira_l edgv.fer_cremalheira_p edgv.fer_girador_ferroviario_p edgv.fer_trecho_ferroviario_l edgv.hdv_atracadouro_terminal_a edgv.hdv_atracadouro_terminal_l edgv.hdv_atracadouro_terminal_p edgv.hdv_eclusa_a edgv.hdv_eclusa_l edgv.hdv_eclusa_p edgv.hdv_fundeadouro_a edgv.hdv_fundeadouro_p edgv.hdv_obstaculo_navegacao_a edgv.hdv_obstaculo_navegacao_l edgv.hdv_obstaculo_navegacao_p edgv.hdv_sinalizacao_p edgv.hdv_trecho_hidroviario_l edgv.hid_area_umida_a edgv.hid_banco_areia_a edgv.hid_banco_areia_l edgv.hid_barragem_a edgv.hid_barragem_l edgv.hid_barragem_p edgv.hid_canal_a edgv.hid_canal_l edgv.hid_comporta_l edgv.hid_comporta_p edgv.hid_corredeira_a edgv.hid_corredeira_l edgv.hid_corredeira_p edgv.hid_dique_a edgv.hid_dique_l edgv.hid_dique_p edgv.hid_fonte_dagua_p edgv.hid_foz_maritima_a edgv.hid_foz_maritima_l edgv.hid_foz_maritima_p edgv.hid_ilha_a edgv.hid_ilha_p edgv.hid_massa_dagua_a edgv.hid_quebramar_molhe_a edgv.hid_quebramar_molhe_l edgv.hid_queda_dagua_a edgv.hid_queda_dagua_l edgv.hid_queda_dagua_p edgv.hid_recife_a edgv.hid_recife_l edgv.hid_recife_p edgv.hid_rocha_em_agua_a edgv.hid_rocha_em_agua_p edgv.hid_sumidouro_vertedouro_p edgv.hid_terreno_sujeito_inundacao_a edgv.hid_trecho_drenagem_l edgv.hid_vala_a edgv.hid_vala_l edgv.laz_arquibancada_a edgv.laz_arquibancada_l edgv.laz_campo_quadra_a edgv.laz_campo_quadra_p edgv.laz_piscina_a edgv.laz_pista_competicao_a edgv.laz_pista_competicao_l edgv.laz_pista_competicao_p edgv.laz_ruina_a edgv.laz_ruina_p edgv.laz_sitio_arqueologico_a edgv.laz_sitio_arqueologico_p edgv.lim_limite_area_especial_l edgv.lim_limite_politico_adm_l edgv.lml_area_densamente_edificada_a edgv.lml_area_pub_militar_a edgv.lml_area_urbana_isolada_a edgv.lml_distrito_a edgv.lml_municipio_a edgv.lml_nome_local_p edgv.lml_pais_a edgv.lml_posic_geo_localidade_p edgv.lml_terra_indigena_a edgv.lml_terra_publica_a edgv.lml_unidade_conservacao_a edgv.lml_unidade_federacao_a edgv.lml_unidade_protecao_integral_a edgv.lml_unidade_uso_sustentavel_a edgv.pto_marco_de_limite_p edgv.pto_pto_est_med_fenomenos_p edgv.pto_pto_geod_topo_controle_p edgv.pto_pto_ref_geod_topo_p edgv.rel_alteracao_fisiografica_antropica_a edgv.rel_alteracao_fisiografica_antropica_l edgv.rel_alteracao_fisiografica_antropica_p edgv.rel_aterro_a edgv.rel_aterro_l edgv.rel_aterro_p edgv.rel_corte_a edgv.rel_corte_l edgv.rel_corte_p edgv.rel_curva_batimetrica_l edgv.rel_curva_nivel_l edgv.rel_dolina_a edgv.rel_dolina_p edgv.rel_duna_a edgv.rel_duna_l edgv.rel_duna_p edgv.rel_elemento_fisiografico_natural_a edgv.rel_elemento_fisiografico_natural_l edgv.rel_elemento_fisiografico_natural_p edgv.rel_gruta_caverna_l edgv.rel_gruta_caverna_p edgv.rel_pico_p edgv.rel_ponto_cotado_altimetrico_p edgv.rel_ponto_cotado_batimetrico_p edgv.rel_rocha_a edgv.rel_rocha_l edgv.rel_rocha_p edgv.rel_terreno_exposto_a edgv.rod_trecho_rodoviario_a edgv.rod_trecho_rodoviario_l edgv.snb_barragem_calcadao_a edgv.snb_dep_abast_agua_a edgv.snb_dep_abast_agua_p edgv.snb_dep_saneamento_a edgv.snb_dep_saneamento_p edgv.tra_caminho_aereo_l edgv.tra_caminho_carrocavel_l edgv.tra_entroncamento_pto_p edgv.tra_funicular_l edgv.tra_passagem_elevada_viaduto_a edgv.tra_passagem_elevada_viaduto_l edgv.tra_passagem_elevada_viaduto_p edgv.tra_passagem_nivel_p edgv.tra_patio_a edgv.tra_ponte_a edgv.tra_ponte_l edgv.tra_ponte_p edgv.tra_travessia_l edgv.tra_travessia_p edgv.tra_travessia_pedestre_l edgv.tra_travessia_pedestre_p edgv.tra_travessia_pedrestre_a edgv.tra_trilha_picada_l edgv.tra_tunel_a edgv.tra_tunel_l edgv.tra_tunel_p edgv.veg_brejo_pantano_a edgv.veg_caatinga_a edgv.veg_campinarana_a edgv.veg_campo_a edgv.veg_cerrado_a edgv.veg_floresta_a edgv.veg_mangue_a edgv.veg_reflorestamento_a edgv.veg_veg_area_contato_a edgv.veg_veg_cultivada_a edgv.veg_veg_restinga_a edgv.ver_arvore_isolada_p edgv.ver_jardim_a
- DestDataset_POSTGIS = mgcp1   # Connection
- SourceDataset_POSTGIS_2 = mgcp1   # Connection
- FEATURE_TYPES_2 = mgcp.aaa010 mgcp.aaa012 mgcp.aaa052 mgcp.aab000 mgcp.aab010 mgcp.aac000 mgcp.aac030 mgcp.aad010 mgcp.aad030 mgcp.aad050 mgcp.aah050 mgcp.aai030 mgcp.aaj010 mgcp.aaj030 mgcp.aaj110 mgcp.aak030 mgcp.aak040 mgcp.aak060 mgcp.aak090 mgcp.aak100 mgcp.aak120 mgcp.aak160 mgcp.aak170 mgcp.aak180 mgcp.aak190 mgcp.aal010 mgcp.aal012 mgcp.aal015 mgcp.aal019 mgcp.aal020 mgcp.aal030 mgcp.aal060 mgcp.aal105 mgcp.aal140 mgcp.aal170 mgcp.aal200 mgcp.aal208 mgcp.aam010 mgcp.aam020 mgcp.aam030 mgcp.aam040 mgcp.aam060 mgcp.aam070 mgcp.aan060 mgcp.aan076 mgcp.aaq040 mgcp.aaq116 mgcp.aaq125 mgcp.aaq130 mgcp.aaq135 mgcp.aaq140 mgcp.aat050 mgcp.aba030 mgcp.aba040 mgcp.aba050 mgcp.abb005 mgcp.abb041 mgcp.abb043 mgcp.abb090 mgcp.abb140 mgcp.abb190 mgcp.abb240 mgcp.abd100 mgcp.abd120 mgcp.abh010 mgcp.abh015 mgcp.abh020 mgcp.abh030 mgcp.abh040 mgcp.abh050 mgcp.abh051 mgcp.abh080 mgcp.abh090 mgcp.abh120 mgcp.abh130 mgcp.abh135 mgcp.abh140 mgcp.abh150 mgcp.abh155 mgcp.abh160 mgcp.abh165 mgcp.abi020 mgcp.abi030 mgcp.abj020 mgcp.abj030 mgcp.abj031 mgcp.abj100 mgcp.abj110 mgcp.ada010 mgcp.adb061 mgcp.adb090 mgcp.adb115 mgcp.adb160 mgcp.adb170 mgcp.adb180 mgcp.adb200 mgcp.aea010 mgcp.aea040 mgcp.aea050 mgcp.aea055 mgcp.aeb010 mgcp.aeb020 mgcp.aec010 mgcp.aec020 mgcp.aec030 mgcp.aec040 mgcp.aec060 mgcp.aed010 mgcp.aed020 mgcp.aed030 mgcp.afa015 mgcp.afa100 mgcp.agb005 mgcp.agb015 mgcp.agb035 mgcp.agb045 mgcp.agb055 mgcp.agb065 mgcp.agb075 mgcp.agb230 mgcp.aquisicao_centroide_vegetacao_p mgcp.aquisicao_limite_vegetacao_l mgcp.asu001 mgcp.azd020 mgcp.laf020 mgcp.lah025 mgcp.lak130 mgcp.lak150 mgcp.lak190 mgcp.lal060 mgcp.lal070 mgcp.lal210 mgcp.lal260 mgcp.lan010 mgcp.lan050 mgcp.lap010 mgcp.lap030 mgcp.lap050 mgcp.laq040 mgcp.laq063 mgcp.laq070 mgcp.laq075 mgcp.laq113 mgcp.laq130 mgcp.lat030 mgcp.lat041 mgcp.lat060 mgcp.lba010 mgcp.lbb041 mgcp.lbb043 mgcp.lbb140 mgcp.lbb190 mgcp.lbb230 mgcp.lbd120 mgcp.lbh010 mgcp.lbh020 mgcp.lbh030 mgcp.lbh060 mgcp.lbh070 mgcp.lbh110 mgcp.lbh120 mgcp.lbh140 mgcp.lbh165 mgcp.lbh180 mgcp.lbi020 mgcp.lbi030 mgcp.lbi040 mgcp.lbi041 mgcp.lbj031 mgcp.lbj040 mgcp.ldb010 mgcp.ldb061 mgcp.ldb070 mgcp.ldb071 mgcp.ldb090 mgcp.ldb100 mgcp.ldb110 mgcp.ldb160 mgcp.ldb200 mgcp.lea020 mgcp.lec030 mgcp.lfa090 mgcp.lgb050 mgcp.paa010 mgcp.paa012 mgcp.paa040 mgcp.paa050 mgcp.pac000 mgcp.pac020 mgcp.pac030 mgcp.pad010 mgcp.pad020 mgcp.pad030 mgcp.pad050 mgcp.paf010 mgcp.paf040 mgcp.paf070 mgcp.pah050 mgcp.pah070 mgcp.paj030 mgcp.paj050 mgcp.paj051 mgcp.paj110 mgcp.pak040 mgcp.pak150 mgcp.pak160 mgcp.pak170 mgcp.pal012 mgcp.pal015 mgcp.pal019 mgcp.pal020 mgcp.pal025 mgcp.pal030 mgcp.pal099 mgcp.pal105 mgcp.pal130 mgcp.pal210 mgcp.pal241 mgcp.pam020 mgcp.pam030 mgcp.pam040 mgcp.pam060 mgcp.pam070 mgcp.pan075 mgcp.pan076 mgcp.paq065 mgcp.paq070 mgcp.paq090 mgcp.paq110 mgcp.paq116 mgcp.paq125 mgcp.pat010 mgcp.pat042 mgcp.pat045 mgcp.pba050 mgcp.pbb155 mgcp.pbd100 mgcp.pbd110 mgcp.pbd130 mgcp.pbd180 mgcp.pbh010 mgcp.pbh070 mgcp.pbh120 mgcp.pbh145 mgcp.pbh170 mgcp.pbh180 mgcp.pbi010 mgcp.pbi020 mgcp.pbi030 mgcp.pbi040 mgcp.pbi041 mgcp.pbi050 mgcp.pbj060 mgcp.pdb029 mgcp.pdb115 mgcp.pdb150 mgcp.pdb160 mgcp.pdb180 mgcp.pec030 mgcp.pga034 mgcp.pgb030 mgcp.pgb040 mgcp.pgb050 mgcp.pgb065 mgcp.pgb220 mgcp.pgb230 mgcp.pgb485 mgcp.psu001 mgcp.pzd040 mgcp.rev_edificacao_a mgcp.rev_edificacao_l mgcp.rev_edificacao_p mgcp.rev_hidrografia_a mgcp.rev_hidrografia_l mgcp.rev_hidrografia_p mgcp.rev_transportes_a mgcp.rev_transportes_l mgcp.rev_transportes_p mgcp.rev_vegetacao_a mgcp.rev_vegetacao_l mgcp.rev_vegetacao_p mgcp.val_edificacao_a mgcp.val_edificacao_l mgcp.val_edificacao_p mgcp.val_hidrografia_a mgcp.val_hidrografia_l mgcp.val_hidrografia_p mgcp.val_transportes_a mgcp.val_transportes_l mgcp.val_transportes_p mgcp.val_vegetacao_a mgcp.val_vegetacao_l mgcp.val_vegetacao_p

Readers:
- POSTGIS_1: POSTGIS from $(SourceDataset_POSTGIS)
- POSTGIS_3: POSTGIS from $(SourceDataset_POSTGIS_2)

Writers:
- POSTGIS_2: POSTGIS to $(DestDataset_POSTGIS)

aaa010 (reader POSTGIS_3)
    attributes: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
Note: Entrada dos dados da EDGV em PostGIS
aer_pista_ponto_pouso_a (reader POSTGIS_1)
    attributes: id serial, altitude float4, extensao float4, geometriaaproximada int2, homologacao int2, largura float4, nome varchar(255), operacional int2, revestimento int2, situacaofisica int2, tipopista int2, usopista int2, necessitamanutencao int2, antropizada int2, mattransp int2, obs varchar(255), tipocemiterio int2, coletiva int2, tipoprodutoresiduo int2, tipovia int2, numerosequencial int4, secundaria int2, codidentificadorunico varchar(255), classificacaoporte int2, tipoobst int2, tipopostofisc int2, canteirodivisorio int2, perimetrooficial float4, orgaoenteresp varchar(255), vaovertical float4,
      latitude varchar(255), tipoptoestmed int2, latitude_gms float4, categoria int2, largurafaixaservidao float4, nrdutos int4, tipotunel int2, pesosuportmaximo float4, especie int2, municipio varchar(255), tiposinal int2, procextracao int2, artificial int2, tipotravessia int2, tipolimpol int2, acostamento int2, regime int2, referencialaltim int2, tipoedifrod int2, codtrechoferrov varchar(255), tipoestgerad int2, emarruamento int2, situacaoespacial int2, obssituacao varchar(255), tipoilha int2, larguramedia float4, meiofio int2, matconstr int2, tipounidprotegida int2, formaextracao int2,
      tipomarcolim int2, sigla varchar(255), destinadoa int2, altitudegeometrica float4, secaoativecon int2, arealegal float4, numeropavimentos int4, tiporecife int2, tipoedifmetroferrov int2, tipotrechoferrov int2, causa int2, coincidecomdentrode int2, vereda int2, classificacao varchar(255), isolada int2, sargeta int2, tipoedifagropec int2, nrfaixas int4, cotacomprovada int2, logradouro varchar(255), calcada int2, tipofontedagua int2, valorgravidade float4, especiepredominante int2, alturaaproximada float4, nrpistas int4, altura float4, longitude_gms float4, posicaorelativa int2, tipolimareaesp int2,
      identificador varchar(255), idtsub varchar(255), tipodepgeral int2, latitudegms float4, tipousoedif int2, caladomaxseca float4, numerometrico int4, atolegal varchar(255), periodicidadeinunda varchar(255), codestacao varchar(255), codponto varchar(255), tipotravessiaped int2, datavisita varchar(255), alturalamina float4, tipoassociado int2, cultivopredominante int2, espacamentoindividuos float4, tipoatracad int2, altitudeortometrica float4, finalidadedep int2, tipocombustivel int2, trafego int2, divisaoativecon int2, aptidaooperacional int2, nrlinhas int2, cultura int2, extensaotrecho float4, dominialidade int2, areaoficial varchar(255), gabhorizsup float4,
      modaluso int2, codident varchar(255), administracao int2, setor int2, gabvertsup float4, posicaopista int2, tipocampo int2, anocriacao varchar(255), tipousocaminhoaer int2, tipopassagviad int2, datamedicao varchar(255), alturaestimada float4, tipolavoura int2, tipoponte int2, tipoexposicao int2, atividade int2, tipotrechoduto int2, tipopistacomp int2, destinacaocemiterio int2, tipocaminhoaereo int2, tipotrechocomunic int2, situacaoemagua int2, tipoedifrelig int2, qualidagua int2, tipoextmin int2, formarocha int2, tipoposte int2, codtrechorod varchar(255), tipoveg int2, datasituacaojuridica varchar(255),
      matcondutor int2, espessura float4, tipoedifturist int2, ensino int2, centrodecarga int2, tipomassadagua int2, navegavel int2, tipopavimentacao int2, codigo varchar(255), tipounidusosust int2, jurisdicao int2, tipoedifaero int2, tipoterrexp int2, emduto int2, historicomodificacoes varchar(255), situacaoagua int2, tipoequipagropec int2, bairro varchar(255), outrarefalt varchar(255), vaolivrehoriz float4, cargasuportmaxima float4, tipocampoquadra int2, unidadefederacao varchar(255), nivelatencao int2, eletrificada int2, tipofundeadouro int2, tipoalterantrop int2, tipoplataforma int2, tipoelevador int2, salgada int2,
      longitudegms float4, unidadevolume int2, mi varchar(255), encoberto int2, sistemageodesico int2, posicaoreledific int2, cota int4, publico int2, turistica int2, trechoemperimetrourbano int2, tiposumvert int2, tipolocalidade int2, finalidade int2, tipoedifabast int2, alturamediaindividuos float4, materialpredominante int2, modalidade int2, usoprincipal int2, codequipdesenvsocial varchar(255), religiao varchar(255), proximidade int2, tipoptorefgeodtopo int2, limitevelocidade float4, sin int2, tipoarea int2, classeativecon int2, localizacaoequipdesenvsocial int2, escala varchar(255), grupoetnico varchar(255), bombeamento int2,
      tipoequipdesenvsocial int2, valorvolume float4, situacaocosta int2, geocodigo varchar(255), terreno int2, outrarefplan varchar(255), tipoediflazer int2, tipotrechodrenagem int2, causaexposicao int2, chamine int2, tipoquebramolhe int2, estadofisico int2, possuitrechodrenagem int2, profundidade int4, cep varchar(255), referencialgrav int2, areavalvulas int2, finalidadepatio int2, tipoedifcomunic int2, tipoconteudo int2, tipoareaumida int2, tipobanco int2, bloco varchar(255), alturatorreaer float4, tiporepdiplomatica int2, tipopocomina int2, tipocurvanivel int2, tipoahe int2, tipoelemnat int2, concessionaria varchar(255),
      tipodelimfis int2, tratamento int2, densidade int2, anodereferencia varchar(255), redereferencia int2, codiso3166 varchar(255), motivodescontinuidade int2, tipoedifsaneam int2, pavimentacao int2, tipoentroncamento int2, tipoedifpubcivil int2, tipoedifenergia int2, orgresp varchar(255), potenciaout float4, inom varchar(255), crista int2, tipouso int2, bitola int2, denominacaoassociada int2, tipoinstalmilitar int2, tombada int2, tipoedifcomercserv int2, tipoembarcacao int2, tipomanguezal int2, tipoqueda int2, desnivel float4, fixa int2, calado float4, tipounidprotinteg int2, situacaomarco int2,
      proprioadm int2, situacaojuridica int2, ceg varchar(255), ovgd int2, tipoproduto int2, longitude varchar(255), grupoativecon int2, tiporef int2, pais varchar(255), depressao int2, tipoedifport int2
    -> Deaggregator
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> SubstringExtractor
Note: DEIXA O NOME DA CLASSE NO PADRÃO DE MAPEAMENTO
SubstringExtractor
    END = -3
    RESULT_ATTR = fme_feature_type
    SRC_STRING = @Value(fme_feature_type)
    START = 0
    -> PythonCaller
PythonCaller
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              file = open(mappingPath, 'r')
              data = file.read()
              mapDict = json.loads(data)
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              return featDict

          def evaluateExpression(self, featDict, expression):
              return expression["nome_atributo"] in featDict and u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  default_key = "atributos_default_ida"
                  filter_key = "filtro_ida"
                  key_class_origin = "classe_ida"
                  key_class_destiny = "classe_volta"
                  key_group_origin = "tupla_ida"
                  key_group_destiny = "tupla_volta"
              else:
                  key_attr_origin = "attr_volta"
                  key_attr_destiny = "attr_ida"
                  key_value_origin = "valor_volta"
                  key_value_destiny = "valor_ida"
                  default_key = "atributos_default_volta"
                  filter_key = "filtro_volta"
                  key_class_origin = "classe_volta"
                  key_class_destiny = "classe_ida"
                  key_group_origin = "tupla_volta"
                  key_group_destiny = "tupla_ida"

              should_map = False
              for classmap in self.mappingDict['mapeamento_classes']:
                  if "sentido" not in classmap or ("sentido" in classmap and classmap["sentido"] == self.mappingType):
                      if classmap[key_class_origin] == featDict["fme_feature_type"]:
                          if filter_key in classmap:
                              if not self.evaluateFilter(featDict, classmap[filter_key]):
                                  continue
                          should_map = True
              if not should_map:
                  featDict["CLASS_NOT_FOUND"] = True
                  return featDict

              mappedFeat = copy.deepcopy(featDict)

              if default_key in self.mappingDict:
                  for default in self.mappingDict[default_key]:
                      mappedFeat[default["nome_atributo"]] = default["valor"]

              if 'mapeamento_atributos' in self.mappingDict:
                  for attmap in self.mappingDict['mapeamento_atributos']:
                      if attmap[key_attr_origin] in featDict:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if 'mapeamento_classes' in self.mappingDict:
                  for classmap in self.mappingDict['mapeamento_classes']:
                      if "sentido" not in classmap or ("sentido" in classmap and classmap["sentido"] == self.mappingType):
                          if classmap[key_class_origin] == featDict["fme_feature_type"]:
                              if filter_key in classmap:
                                  if not self.evaluateFilter(featDict, classmap[filter_key]):
                                      continue

                              mappedFeat["fme_feature_type"] = classmap[key_class_destiny]

                              if default_key in classmap:
                                  for default in classmap[default_key]:
                                      mappedFeat[default["nome_atributo"]] = default["valor"]

                              if "traducao_atributos" in classmap:
                                  for attmap in classmap['traducao_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_atributos" in classmap:
                                  for attmap in classmap['mapeamento_atributos']:
                                      if "sentido" not in attmap or ("sentido" in attmap and attmap["sentido"] == self.mappingType):
                                          if all([self.evaluateExpression(featDict, condition) for condition in attmap[key_group_origin]]):
                                              for valuemap in attmap[key_group_destiny]:
                                                  mappedFeat[valuemap["nome_atributo"]] = valuemap["valor"]
                              break

              return mappedFeat

          def mapDictToFeature(self, feat, featDict):
              for attr, value in featDict.iteritems():
                  if value or value == 0:
                      feat.setAttribute(attr, u'{0}'.format(value))
                  else:
                      feat.setAttribute(attr, None)
              return feat

          def input(self,feature):
              feat = self.buildFeatureDict(feature)
              outputFeatDict = self.convertFeature(feat)
              if "CLASS_NOT_FOUND" in outputFeatDict and not outputFeatDict["CLASS_NOT_FOUND"]:
                  feature.setAttribute("CLASS_NOT_FOUND", u'True')
                  self.pyoutput(feature)
              else:
                  outputFeature = self.mapDictToFeature(feature, outputFeatDict)
                  self.pyoutput(outputFeature)

          def close(self):
              pass
    PYTHONSYMBOL = FeatureProcessor
    -> Tester_4
Note: VERIFICA SE FOI ENCONTRADA CORRESPONDÊNCIA DE CLASSE NA SAÍDA
Tester_4
    BOOL_OP = OR
    COMPOSITE_TEST = 1
    TEST_CLAUSE = TEST @Value(CLASS_NOT_FOUND) = True
    TEST_MODE = TEST
    PASSED -> NÃO_MAPEADO
    FAILED -> Counter
Reprojector
    DEST = EPSG:4326
    INTERPOLATION_TYPE_NAME = Nearest Neighbor
    RASTER_CELL_SIZE = Preserve Cells
    RASTER_TOLERANCE = 0.0
    SOURCE = Read from feature
    REPROJECTED -> Table1 (writer POSTGIS_2)
Table1 (writer POSTGIS_2)
Note: CLASSES SEM CORRESPONDÊNCIA
NÃO_MAPEADO: Inspector

Bookmark: DSGTools as geometrias são multi
Counter
    CNT_ATTR = _count
    DOMAIN = counter
    SCOPE = Global
    START = 0
    -> Aggregator
Aggregator
    ACCUM_ATTRS_NAME = Use Attributes From One Feature
    AGGREGATE_TYPE = Homogeneous Collection (If Possible)
    GROUP_BY = _count
    MODE = Geometry - Assemble One Level
    ORDERED = Yes
    SEP = ,
    AGGREGATE -> AttributeCreator_4

Bookmark: Quebra as classes por tipo de geometria e ajusta o fme_feature_type de acordo
Note: deixa minusculo o nome da classe do MGCP para ficar conforme o banco
AttributeCreator_4
    ATTR_TABLE = SET_TO fme_feature_type = @LowerCase(@Value(fme_feature_type))
    -> BulkAttributeRenamer
Note: Deixa minusculo o nome do atributo do MGCP para ficar conforme o banco
BulkAttributeRenamer
    ATTRCHOICE = All Attributes
    CASE_CHANGE_TYPE = lower
    MODE_CHOICE = RENAME
    PATTERN_ACTION_DISP = CASECHANGE
    -> GeometryFilter
GeometryFilter
    BREAK_AGG = No
    GEOM_PORT_NAMES = Point Line Area
    POINT -> AttributeCreator
    LINE -> AttributeCreator_2
    AREA -> AttributeCreator_3
Note: Deixa o nome da classe com geometria no padrão do MGCP e adiciona o schema
AttributeCreator
    ATTR_TABLE = SET_TO fme_feature_type = mgcp.p@Value(fme_feature_type)
    -> Reprojector
AttributeCreator_2
    ATTR_TABLE = SET_TO fme_feature_type = mgcp.l@Value(fme_feature_type)
    -> Reprojector
AttributeCreator_3
    ATTR_TABLE = SET_TO fme_feature_type = mgcp.a@Value(fme_feature_type)
    -> Reprojector
