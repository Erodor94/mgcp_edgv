FME workspace fme_mapeamento_MGCP_2_EDGV_30_ida.fmw

Parameters:
- direcao = ida   # Direção do mapeamento
- JsonMapeamento = $(FME_MF_DIR)Novo_MGCP-EDGV_final_2019-07-08.json   # Arquivo de mapeamento
- COORDSYS = EPSG:4674   # Sistema de coordenada da entrada
- SourceDataset_ESRISHAPE = ""$(FME_MF_DIR)W058S21\AAJ030.shp" "$(FME_MF_DIR)W058S21\AAL015.shp" "$(FME_MF_DIR)W058S21\ABA030.shp" "$(FME_MF_DIR)W058S21\ABH080.shp" "$(FME_MF_DIR)W058S21\ABH090.shp" "$(FME_MF_DIR)W058S21\ABH130.shp" "$(FME_MF_DIR)W058S21\ABH140.shp" "$(FME_MF_DIR)W058S21\AEB010.shp" "$(FME_MF_DIR)W058S21\AEB020.shp" "$(FME_MF_DIR)W058S21\AEC030.shp" "$(FME_MF_DIR)W058S21\AED010.shp" "$(FME_MF_DIR)W058S21\AED020.shp" "$(FME_MF_DIR)W058S21\AGB005.shp" "$(FME_MF_DIR)W058S21\AGB015.shp" "$(FME_MF_DIR)W058S21\AGB055.shp" "$(FME_MF_DIR)W058S21\LAP010.shp" "$(FME_MF_DIR)W058S21\LAP030.shp" "$(FME_MF_DIR)W058S21\LAP050.shp" "$(FME_MF_DIR)W058S21\LAQ040.shp" "$(FME_MF_DIR)W058S21\LAQ070.shp" "$(FME_MF_DIR)W058S21\LBH030.shp" "$(FME_MF_DIR)W058S21\LBH070.shp" "$(FME_MF_DIR)W058S21\LBH140.shp" "$(FME_MF_DIR)W058S21\LBI020.shp" "$(FME_MF_DIR)W058S21\PAJ030.shp" "$(FME_MF_DIR)W058S21\PAL015.shp" "$(FME_MF_DIR)W058S21\PAL019.shp" "$(FME_MF_DIR)W058S21\PAL020.shp" "$(FME_MF_DIR)W058S21\PAL099.shp" "$(FME_MF_DIR)W058S21\PAL241.shp" "$(FME_MF_DIR)W058S21\PAM020.shp" "$(FME_MF_DIR)W058S21\PAM070.shp" "$(FME_MF_DIR)W058S21\PAQ065.shp" "$(FME_MF_DIR)W058S21\PBH070.shp" "$(FME_MF_DIR)W058S21\PBH145.shp" "$(FME_MF_DIR)W058S21\PBH170.shp" "$(FME_MF_DIR)W058S21\PBI010.shp" "$(FME_MF_DIR)W058S21\PGB230.shp" "$(FME_MF_DIR)W058S21\PZD040.shp""   # Source Esri Shapefile(s)
- FEATURE_TYPES =
- SourceDataset_POSTGIS = edgv_pid   # Connection
- DestDataset_POSTGIS = edgv_pid   # Connection

Readers:
- ESRISHAPE_1: ESRISHAPE from $(SourceDataset_ESRISHAPE)
- POSTGIS_1: POSTGIS from $(SourceDataset_POSTGIS)

Writers:
- POSTGIS_2: POSTGIS to $(DestDataset_POSTGIS)

AAJ030 (reader ESRISHAPE_1)
    attributes: FCODE char(5), UID char(36), ACC long, CCN char(254), SDV char(20), SDP char(254), SRT long, TXT char(254), NFN char(18), HWT long, TTC long, SSC long, IKO char(254), DMB double, FFN long, LEN double, CON long, CNS long, LOC long, BOT long, FUC long, WTC long, TRE long, SFS long, FPT long, VEG long, HYP long, WID double, ORD long, BSC long,
      NAM char(80), VOI char(36), NOS long, PPO long, WCC long, OHB double, DMT double, VSP long, AOO double, TID long, HGT double, CDA long, PRM long, ZVA double, WD1 double, SEP long, MCC long, MES long, FUN long, TRS long, RST long, AZC long, NFI char(18), LTN long, BAC long, SCC long, SWT long, WST long, CAA long, HCT long,
      COD long
    -> CoordinateSystemSetter
Note: DEFINE O SRC DA ENTRADA
CoordinateSystemSetter
    COORDSYS = $(COORDSYS)
    -> SubstringExtractor
Note: DEIXA O NOME DA CLASSE NO PADRÃO DE MAPEAMENTO
SubstringExtractor
    END = -1
    RESULT_ATTR = fme_feature_type
    SRC_STRING = @Value(fme_feature_type)
    START = 1
    -> PythonCaller
PythonCaller
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              file = open(mappingPath, 'r')
              data = file.read()
              mapDict = json.loads(data)
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                  print feature.performFunction('@GeometryType()')
              return featDict

          def evaluateExpression(self, featDict, expression):
              return expression["nome_atributo"] in featDict and str(featDict[expression["nome_atributo"]]) == str(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  default_key = "atributos_default_ida"
                  filter_key = "filtro_ida"
                  key_class_origin = "classe_ida"
                  key_class_destiny = "classe_volta"
                  key_group_origin = "tupla_ida"
                  key_group_destiny = "tupla_volta"
              else:
                  key_attr_origin = "attr_volta"
                  key_attr_destiny = "attr_ida"
                  key_value_origin = "valor_volta"
                  key_value_destiny = "valor_ida"
                  default_key = "atributos_default_volta"
                  filter_key = "filtro_volta"
                  key_class_origin = "classe_volta"
                  key_class_destiny = "classe_ida"
                  key_group_origin = "tupla_volta"
                  key_group_destiny = "tupla_ida"

              should_map = False
              for classmap in self.mappingDict['mapeamento_classes']:
                  if "sentido" not in classmap or ("sentido" in classmap and classmap["sentido"] == self.mappingType):
                      if classmap[key_class_origin] == featDict["fme_feature_type"]:
                          if filter_key in classmap:
                              if not self.evaluateFilter(featDict, classmap[filter_key]):
                                  continue
                          should_map = True
              if not should_map:
                  featDict["CLASS_NOT_FOUND"] = True
                  return featDict

              mappedFeat = copy.deepcopy(featDict)

              for attmap in self.mappingDict['mapeamento_atributos']:
                  if attmap[key_attr_origin] in featDict:
                      mappedFeat[attmap[key_attr_destiny]] = featDict[attmap[key_attr_origin]]
                      if "traducao" in attmap:
                          for valuemap in attmap["traducao"]:
                              if str(valuemap[key_value_origin]) == str(featDict[attmap[key_attr_origin]]) and ("sentido" not in valuemap or ("sentido" in valuemap and valuemap["sentido"] == self.mappingType)):
                                  mappedFeat[attmap[key_attr_destiny]] = valuemap[key_value_destiny]

              for classmap in self.mappingDict['mapeamento_classes']:
                  if "sentido" not in classmap or ("sentido" in classmap and classmap["sentido"] == self.mappingType):
                      if classmap[key_class_origin] == featDict["fme_feature_type"]:
                          if filter_key in classmap:
                              if not self.evaluateFilter(featDict, classmap[filter_key]):
                                  continue

                          mappedFeat["fme_feature_type"] = classmap[key_class_destiny]

                          if default_key in classmap:
                              for default in classmap[default_key]:
                                  mappedFeat[default["nome_atributo"]] = default["valor"]

                          if "traducao_atributos" in classmap:
                              for attmap in classmap['traducao_atributos']:
                                  if attmap[key_attr_origin] in featDict:
                                      if attmap[key_attr_destiny] not in mappedFeat:
                                          mappedFeat[attmap[key_attr_destiny]] = featDict[attmap[key_attr_origin]]
                                      if "traducao" in attmap:
                                          for valuemap in attmap["traducao"]:
                                              if str(valuemap[key_value_origin]) == str(featDict[attmap[key_attr_origin]]) and ("sentido" not in valuemap or ("sentido" in valuemap and valuemap["sentido"] == self.mappingType)):
                                                  mappedFeat[attmap[key_attr_destiny]] = valuemap[key_value_destiny]

                          if "mapeamento_atributos" in classmap:
                              for attmap in classmap['mapeamento_atributos']:
                                  if "sentido" not in attmap or ("sentido" in attmap and attmap["sentido"] == self.mappingType):
                                      if all([self.evaluateExpression(featDict, condition) for condition in attmap[key_group_origin]]):
                                          for valuemap in attmap[key_group_destiny]:
                                              mappedFeat[valuemap["nome_atributo"]] = valuemap["valor"]
                          break

              return mappedFeat

          def mapDictToFeature(self, feat, featDict):
              for attr, value in featDict.iteritems():
                  if value or value == 0:
                      feat.setAttribute(attr, u'{0}'.format(value))
                  else:
                      feat.setAttribute(attr, None)
              return feat

          def input(self,feature):
              feat = self.buildFeatureDict(feature)
              outputFeatDict = self.convertFeature(feat)
              if "CLASS_NOT_FOUND" in outputFeatDict and not outputFeatDict["CLASS_NOT_FOUND"]:
                  feature.setAttribute("CLASS_NOT_FOUND", u'True')
                  self.pyoutput(feature)
              else:
                  outputFeature = self.mapDictToFeature(feature, outputFeatDict)
                  self.pyoutput(outputFeature)

          def close(self):
              pass
    PYTHONSYMBOL = FeatureProcessor
    -> Tester_4
Note: VERIFICA SE FOI ENCONTRADA CORRESPONDÊNCIA DE CLASSE NA SAÍDA
Tester_4
    BOOL_OP = OR
    COMPOSITE_TEST = 1
    TEST_CLAUSE = TEST @Value(CLASS_NOT_FOUND) = True
    TEST_MODE = TEST
    PASSED -> NÃO_MAPEADO
    FAILED -> Counter
Table1 (writer POSTGIS_2)
Note: CLASSES SEM CORRESPONDÊNCIA
NÃO_MAPEADO: Inspector

Bookmark: DSGTools as geometrias são multi
Counter
    CNT_ATTR = _count
    DOMAIN = counter
    SCOPE = Global
    START = 0
    -> Aggregator
Aggregator
    ACCUM_ATTRS_NAME = Use Attributes From One Feature
    AGGREGATE_TYPE = Homogeneous Collection (If Possible)
    GROUP_BY = _count
    MODE = Geometry - Assemble One Level
    ORDERED = Yes
    SEP = ,
    AGGREGATE -> GeometryFilter

Bookmark: Quebra as classes por tipo de geometria e ajusta o fme_feature_type de acordo
GeometryFilter
    BREAK_AGG = No
    GEOM_PORT_NAMES = Point Line Area
    POINT -> AttributeCreator
    LINE -> AttributeCreator_2
    AREA -> AttributeCreator_3
AttributeCreator
    ATTR_TABLE = SET_TO fme_feature_type = @Value(fme_feature_type)_p
    -> Table1 (writer POSTGIS_2)
AttributeCreator_2
    ATTR_TABLE = SET_TO fme_feature_type = @Value(fme_feature_type)_l
    -> Table1 (writer POSTGIS_2)
AttributeCreator_3
    ATTR_TABLE = SET_TO fme_feature_type = @Value(fme_feature_type)_a
    -> Table1 (writer POSTGIS_2)
